module ietf-tls-client {
  yang-version 1;

  namespace "urn:ietf:params:xml:ns:yang:ietf-tls-client";
  prefix "tlsc";

  import ietf-tls-common {
    prefix tlscmn;
    revision-date 2017-10-30; // stable grouping definitions
    //reference
    //  "RFC XXXX: YANG Groupings for TLS Clients and TLS Servers";
  }

  import ietf-keystore {
    prefix ks;
    //reference
    //  "RFC YYYY: Keystore Model";
  }

  import ietf-inet-types { prefix inet; }


  organization
   "IETF NETCONF (Network Configuration) Working Group";

  contact
   "WG Web:   <http://tools.ietf.org/wg/netconf/>
    WG List:  <mailto:netconf@ietf.org>

    Author:   Kent Watsen
              <mailto:kwatsen@juniper.net>

    Author:   Gary Wu
              <mailto:garywu@cisco.com>";

  description
   "This module defines a reusable grouping for a TLS client that
    can be used as a basis for specific TLS client instances.

    Copyright (c) 2017 IETF Trust and the persons identified as
    authors of the code. All rights reserved.

    Redistribution and use in source and binary forms, with or
    without modification, is permitted pursuant to, and subject
    to the license terms contained in, the Simplified BSD
    License set forth in Section 4.c of the IETF Trust's
    Legal Provisions Relating to IETF Documents
    (http://trustee.ietf.org/license-info).

    This version of this YANG module is part of RFC XXXX; see
    the RFC itself for full legal notices.";

  revision "2017-10-30" {
    description
     "Initial version";
    reference
     "RFC XXXX: YANG Groupings for TLS Clients and TLS Servers";
  }

  // features

  feature tls-client-hello-params-config {
    description
      "TLS hello message parameters are configurable on a TLS
       client.";
  }

  // groupings

  //grouping tls-client-grouping {
  //  description
  //    "A reusable grouping for configuring a TLS client without
  //     any consideration for how an underlying TCP session is
  //     established.";

  
  list ietf-client-configurations {
  key "id";
  
  leaf id {
    type uint8;
  }
  
  container ietf-tls-client {

  container connection-info {
      leaf server-address {
      type inet:ip-address;
      mandatory true;
      description "Server IPv4 address";
    }

    leaf server-port {
      type inet:port-number;
      description "Server port";
    }

    leaf auto-start {
      type boolean;
      description "If true, the client will start immediately.";
    }
  }

    container client-identity {
      description
        "The credentials used by the client to authenticate to
         the TLS server.";

      choice auth-type {
        description
          "The authentication type.";
        container certificate {
          uses ks:private-key-grouping;
          uses ks:certificate-grouping;
          description
            "Choice statement for future augmentations.";
        }
      }
    }

    container server-auth {
      must 'pinned-ca-certs or pinned-server-certs';
      description
        "Trusted server identities.";
      container pinned-ca-certs {
        //type ks:pinned-certificates;
        uses ks:certificate-grouping;
        description
        "A reference to a list of certificate authority (CA)
         certificates used by the TLS client to authenticate
         TLS server certificates.  A server certificate is
         authenticated if it has a valid chain of trust to
         a configured pinned CA certificate.";
      }
      container pinned-server-certs {
        //type ks:pinned-certificates;
        uses ks:certificate-grouping;
        description
        "A reference to a list of server certificates used by
         the TLS client to authenticate TLS server certificates.
         A server certificate is authenticated if it is an
         exact match to a configured pinned server certificate.";
      }
    }

    container hello-params {
      //if-feature tls-client-hello-params-config;
      uses tlscmn:hello-params-grouping;
      description
        "Configurable parameters for the TLS hello message.";
    }
  }
 }

 // } // end tls-client-grouping

 rpc init_ssl_client {
       input {
        leaf id {
          type uint8;
          description "SSL configuration to load and run";
        }
       }
       output {
           leaf status {
               type string;
               description "Status response";
           }
       }
   }


}
